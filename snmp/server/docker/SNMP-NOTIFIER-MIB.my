SNMP-NOTIFIER-MIB DEFINITIONS ::= BEGIN

IMPORTS
    MODULE-IDENTITY, enterprises FROM SNMPv2-SMI;

snmpNotifier MODULE-IDENTITY
    LAST-UPDATED "202201070000Z"
    ORGANIZATION "SNMP Notifier"
    CONTACT-INFO
        "SNMP Notifier

        https://github.com/maxwo/snmp_notifier/

        "

    DESCRIPTION
        "This MIB contains definition of the SNMP Traps
        associated to alerts sent by the SNMP Notifier"

    REVISION
        "201912260000Z"

    DESCRIPTION
        "First revision that includes only the alerts subtree"
::= { enterprises 98789 }

snmpNotifierAlertsObjects OBJECT IDENTIFIER ::= { snmpNotifier 2 }

snmpNotifierAlertId OBJECT-TYPE
    SYNTAX      DisplayString
    MAX-ACCESS  accessible-for-notify
    STATUS      current
    DESCRIPTION "The ID of the SNMP notifier alert."
::= { snmpNotifierAlertsObjects 1 }

snmpNotifierAlertSeverity OBJECT-TYPE
    SYNTAX      DisplayString
    MAX-ACCESS  accessible-for-notify
    STATUS      current
    DESCRIPTION "The severity of the SNMP notifier alert."
::= { snmpNotifierAlertsObjects 2 }

snmpNotifierAlertDescription OBJECT-TYPE
    SYNTAX      DisplayString
    MAX-ACCESS  accessible-for-notify
    STATUS      current
    DESCRIPTION "The description of the SNMP notifier alert."
::= { snmpNotifierAlertsObjects 3 }

snmpNotifierDefaultTrap NOTIFICATION-TYPE
    OBJECTS {
        snmpNotifierAlertId,
        snmpNotifierAlertSeverity,
        snmpNotifierAlertDescription
    }
    STATUS current
    DESCRIPTION "The default SNMP notifier notification"
    ::= { snmpNotifier 1 }
END
